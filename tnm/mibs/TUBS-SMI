TUBS-SMI DEFINITIONS ::= BEGIN

-- @(#) $Id: TUBS-SMI,v 1.1.1.1 2006/12/07 12:16:58 karl Exp $

IMPORTS
    MODULE-IDENTITY, OBJECT-IDENTITY, enterprises
	FROM SNMPv2-SMI;

tubs MODULE-IDENTITY
    LAST-UPDATED "200002090000Z"
    ORGANIZATION "TU Braunschweig"
    CONTACT-INFO
	"Juergen Schoenwaelder
	 TU Braunschweig
	 Bueltenweg 74/75
	 38108 Braunschweig
	 Germany

	 Tel: +49 531 391 3249
	 Fax: +49 531 391 5936
	 E-mail: schoenw@ibr.cs.tu-bs.de"
    DESCRIPTION
	"The toplevel OID registration for the Technical University
	 of Braunschweig, Germany."
    REVISION	"200002090000Z"
    DESCRIPTION
	"Changed the module name from TUBS-REGISTRATION to TUBS-SMI."
    REVISION	"9702141023Z"
    DESCRIPTION
	"The initial revision."
    ::= { enterprises 1575 }

ibr OBJECT-IDENTITY
    STATUS	current
    DESCRIPTION
	"The subtree delegated to the Department of Operating Systems
	 and Computer Networks (Institut fuer Betriebssysteme und
	 Rechnerverbund)."
    ::= { tubs 1 }

-- Allocations below TUBS-SMI::ibr:
--
--   1  TUBS-IBR-TNM-MIB::tnmMIB
--   2  TUBS-IBR-NFS-MIB::nfsMIB
--   3  TUBS-IBR-PROC-MIB::procMIB
--   4  <obsolete>
--   5	TUBS-IBR-LINUX-MIB::linuxMIB
--   6  TUBS-IBR-AGENT-CAPABILITIES::ibrAgentCapabilities
--   7  TUBS-IBR-TEST-MIB::testMIB
--   8	<obsolete>
--   9  LIBSMI-TEST-MIB::testMib

END
